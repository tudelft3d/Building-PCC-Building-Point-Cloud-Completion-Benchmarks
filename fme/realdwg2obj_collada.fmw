FME workspace realdwg2obj_collada.fmw

Parameters:
- SourceDataset_REALDWG = D:\3DBAG_PCC\Rotterdam\dwg\Rozenburg\Gebouwen\Noordzeeweg.dwg   # Source Autodesk AutoCAD RealDWG File(s)
- DestDataset_OBJ = D:\3DBAG_PCC\Rotterdam\obj_buildings\Rozenburg\obj   # Destination OBJ Folder
- DestDataset_COLLADA = D:\3DBAG_PCC\Rotterdam\obj_buildings\Rozenburg\dae   # Destination COLLADA Folder

Readers:
- REALDWG_1: REALDWG from $(SourceDataset_REALDWG)

Writers:
- OBJ_1: OBJ to $(DestDataset_OBJ)
- COLLADA_1: COLLADA to $(DestDataset_COLLADA)

Gebouwen (reader REALDWG_1)
    -> SubstringExtractor
SubstringExtractor
    END = -1
    RESULT_ATTR = PandID_new
    SRC_STRING = @Value(autocad_extended_data_list{1})
    START = 15
    -> Gebouwen (writer OBJ_1)
    -> Gebouwen (writer COLLADA_1) [off]
Gebouwen (writer OBJ_1)
Gebouwen (writer COLLADA_1) [off]
