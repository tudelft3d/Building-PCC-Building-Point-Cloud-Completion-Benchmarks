FME workspace las_merge.fmw
Title: FileNameMatch

Parameters:
- SourceDataset_LAS = C:\data\PhDthesis\git_pcc_data\data\Rotterdam_processed\las_3\ahn4\BAG_0599100000069166.las   # Source ASPRS LAS File(s)
- SourceDataset_LAS_3 = C:\data\PhDthesis\git_pcc_data\data\Rotterdam_processed\las_3c\ahn4\BAG_0599100000069166.las   # Source ASPRS LAS File(s)
- DestDataset_LAS = C:\data\PhDthesis\git_pcc_data\data\Rotterdam_processed\las_0_3\ahn4   # Destination ASPRS LAS Folder

Readers:
- LAS_1: LAS from $(SourceDataset_LAS)
- LAS_2: LAS from $(SourceDataset_LAS_3)

Writers:
- LAS_3: LAS to $(DestDataset_LAS)

LAS (reader LAS_1)
    -> PointCloudCombiner
LAS (reader LAS_2)
    -> PointCloudCombiner
PointCloudCombiner
    ACCUM_ATTRS_NAME = Yes
    EXTRACT_RASTER_NODATA_NAME = No
    GROUP_BY = fme_basename
    SPACING = 1.0
    -> LAS (writer LAS_3)
LAS (writer LAS_3)
