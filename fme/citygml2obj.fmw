FME workspace citygml2obj.fmw

Parameters:
- SourceDataset_CITYGML = C:\data\PhDthesis\git_pcc_data\data\denhaag\den_haag_3d_centrum_deel_4.gml   # Source CityGML File(s)
- DestDataset_OBJ_3 = C:\data\PhDthesis\git_pcc_data\data\denhaag\obj   # Destination OBJ Folder
- DestDataset_OBJ = C:\data\PhDthesis\git_pcc_data\data\denhaag\obj   # Destination OBJ Folder

Readers:
- CITYGML_1: CITYGML from $(SourceDataset_CITYGML)

Writers:
- OBJ_1: OBJ to $(DestDataset_OBJ)
- OBJ_2: OBJ to $(DestDataset_OBJ_3)

Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, Dakoppervlakte xml_buffer, GEB_DOEL xml_buffer, Muuroppervlakte xml_buffer, Vloeroppervlakte xml_buffer, Volume xml_buffer, hoogte_Z_max_in_m_NAP xml_buffer
    -> Building (writer OBJ_2)
Building (writer OBJ_2)
