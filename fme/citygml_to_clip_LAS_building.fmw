FME workspace citygml_to_clip_LAS_building.fmw

Parameters:
- DestDataset_OGCGEOPACKAGE = C:\data\PhDthesis\git_pcc_data\data\rotterdam\clip\shp\test.gpkg   # GeoPackage File
- SourceDataset_LAS = C:\data\PhDthesis\git_pcc_data\data\denhaag\C_30GN1_building.LAZ   # Source ASPRS LAS File(s)
- DestDataset_LAS = C:\data\PhDthesis\git_pcc_data\data\denhaag\clip   # Destination ASPRS LAS Folder
- DestDataset_SHAPEFILE = C:\data\PhDthesis\git_pcc_data\data\rotterdam\clip\shp   # Destination Esri Shapefile Folder
- SourceDataset_CITYGML = C:\data\PhDthesis\git_pcc_data\data\denhaag\den_haag_3d_oostduinen.gml   # Source CityGML File(s)

Readers:
- LAS_1: LAS from $(SourceDataset_LAS)
- CITYGML_1: CITYGML from $(SourceDataset_CITYGML)

Writers:
- OGCGEOPACKAGE_1: OGCGEOPACKAGE to $(DestDataset_OGCGEOPACKAGE)
- LAS_2: LAS to $(DestDataset_LAS)
- SHAPEFILE_1: SHAPEFILE to $(DestDataset_SHAPEFILE)

Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, Dakoppervlakte xml_buffer, GEB_DOEL xml_buffer, Muuroppervlakte xml_buffer, Vloeroppervlakte xml_buffer, Volume xml_buffer, hoogte_Z_max_in_m_NAP xml_buffer
    -> SurfaceFootprintReplacer
SurfaceFootprintReplacer
    OFFSET_Z = 0
    SHADOW_MODE = Overhead Shadow
    FOOTPRINT -> GeometryFilter
GeometryFilter
    FILTER_MODE = SIMPLE
    FILTER_MULTI = FILTER_TYPES]Area]FME_CONTROLLER_QUERY_FILE]]FME_CONTROLLER_CHOICE]Simple
    Area -> AreaGapAndOverlapCleaner
AreaGapAndOverlapCleaner
    CLEANING_TOLERANCE = Automatic
    CONNECT_Z_MODE = First Wins
    DEAGGREGATE_INPUT = YES
    FILL_ALL_GAPS = Yes
    GROUP_BY = gml_id
    MEASURE_TYPE = Continuous
    MISSING_VAL_MODE = Compute
    REPAIR_METHOD = Longest Boundary
    REPAIRED -> Dissolver
Dissolver
    ACCUM_INPUT_ATTRS = Use Attributes From One Feature
    CLEANING_TOLERANCE = Automatic
    CONNECT_Z_MODE = Extend
    DEAGGREGATE_INPUT = Yes
    GROUP_BY = gml_id
    AREA -> Gebouwen (writer OGCGEOPACKAGE_1) [off]
    AREA -> Clipper [CLIPPER]
    AREA -> Gebouwen (writer SHAPEFILE_1) [off]
Gebouwen (writer OGCGEOPACKAGE_1) [off]
    attributes: PandID text
Gebouwen (writer SHAPEFILE_1) [off]
    attributes: autocad_ex varchar(50)
LAS (reader LAS_1)
    -> Clipper [CANDIDATE]
Clipper
    ADD_NODATA = YES
    ATTR_ACCUM_MODE = CLIPPER_ONLY
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Gebouwen00 (writer LAS_2)
Gebouwen00 (writer LAS_2)
