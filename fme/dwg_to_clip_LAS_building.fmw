FME workspace dwg_to_clip_LAS_building.fmw

Parameters:
- SourceDataset_REALDWG = C:\data\PhDthesis\git_pcc_data\data\rotterdam\test\Maasvlakte.dwg   # Source Autodesk AutoCAD RealDWG File(s)
- DestDataset_OGCGEOPACKAGE = C:\data\PhDthesis\git_pcc_data\data\rotterdam\clip\shp\test.gpkg   # GeoPackage File
- SourceDataset_LAS = C:\data\PhDthesis\git_pcc_data\data\rotterdam\test\C_37AZ1_building.LAZ   # Source ASPRS LAS File(s)
- DestDataset_LAS = C:\data\PhDthesis\git_pcc_data\data\rotterdam\clip\in   # Destination ASPRS LAS Folder
- DestDataset_SHAPEFILE = C:\data\PhDthesis\git_pcc_data\data\rotterdam\clip\shp   # Destination Esri Shapefile Folder

Readers:
- REALDWG_1: REALDWG from $(SourceDataset_REALDWG)
- LAS_1: LAS from $(SourceDataset_LAS)

Writers:
- OGCGEOPACKAGE_1: OGCGEOPACKAGE to $(DestDataset_OGCGEOPACKAGE)
- LAS_2: LAS to $(DestDataset_LAS)
- SHAPEFILE_1: SHAPEFILE to $(DestDataset_SHAPEFILE)

Gebouwen (reader REALDWG_1)
    -> SubstringExtractor
SubstringExtractor
    END = -1
    RESULT_ATTR = PandID_new
    SRC_STRING = @Value(autocad_extended_data_list{1})
    START = 15
    -> SurfaceFootprintReplacer
SurfaceFootprintReplacer
    OFFSET_Z = 0
    SHADOW_MODE = Overhead Shadow
    FOOTPRINT -> GeometryFilter
GeometryFilter
    FILTER_MODE = SIMPLE
    FILTER_MULTI = FILTER_TYPES]Area]FME_CONTROLLER_QUERY_FILE]]FME_CONTROLLER_CHOICE]Simple
    Area -> AreaGapAndOverlapCleaner
AreaGapAndOverlapCleaner
    CLEANING_TOLERANCE = Automatic
    CONNECT_Z_MODE = First Wins
    DEAGGREGATE_INPUT = YES
    FILL_ALL_GAPS = Yes
    GROUP_BY = PandID_new
    MEASURE_TYPE = Continuous
    MISSING_VAL_MODE = Compute
    REPAIR_METHOD = Longest Boundary
    REPAIRED -> Dissolver
Dissolver
    ACCUM_INPUT_ATTRS = Use Attributes From One Feature
    CLEANING_TOLERANCE = Automatic
    CONNECT_Z_MODE = Extend
    DEAGGREGATE_INPUT = Yes
    GROUP_BY = PandID_new
    AREA -> Gebouwen (writer OGCGEOPACKAGE_1) [off]
    AREA -> Clipper [CLIPPER]
    AREA -> Gebouwen (writer SHAPEFILE_1) [off]
Gebouwen (writer OGCGEOPACKAGE_1) [off]
    attributes: PandID text
Gebouwen (writer SHAPEFILE_1) [off]
    attributes: autocad_ex varchar(50)
LAS (reader LAS_1)
    -> Clipper [CANDIDATE]
Clipper
    ADD_NODATA = YES
    ATTR_ACCUM_MODE = CLIPPER_ONLY
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Gebouwen00 (writer LAS_2)
Gebouwen00 (writer LAS_2)
